(vl-load-com)

(defun ns-replace-safe (replacement search value / position)
  (while (setq position (vl-string-search search value))
    (setq value (strcat (substr value 1 position) replacement (substr value (+ position (strlen search) 1))))
  )
  value
)

(defun ns-json-string (value / index character escaped)
  (setq value (if value (vl-princ-to-string value) ""))
  (setq value (ns-replace-safe "PH" "\\U+0278" value))
  (setq value (ns-replace-safe " DEG " "\\U+00B0" value))
  (setq value (ns-replace-safe "U+" "\\U+" value))
  (setq index 1 escaped "")
  (while (<= index (strlen value))
    (setq character (substr value index 1))
    (setq escaped
      (strcat escaped
        (cond
          ((= (ascii character) 92) "\\\\")
          ((= (ascii character) 34) "\\\"")
          ((= (ascii character) 10) "\\n")
          ((= (ascii character) 13) "\\r")
          ((= (ascii character) 9) "\\t")
          (T character)
        )
      )
    )
    (setq index (1+ index))
  )
  (strcat "\"" escaped "\"")
)

(defun ns-value (code data / pair) (setq pair (assoc code data)) (if pair (cdr pair) ""))
(defun ns-write-line (value) (write-line value ns-output-file))
(defun ns-point-json (point) (if (and (listp point) (numberp (car point))) (strcat "[" (rtos (car point) 2 6) "," (rtos (cadr point) 2 6) "," (rtos (if (caddr point) (caddr point) 0.0) 2 6) "]") "[]"))

(defun ns-bounds-json (entity / object result minimum maximum)
  (setq object (vl-catch-all-apply 'vlax-ename->vla-object (list entity)))
  (if (vl-catch-all-error-p object)
    "[]"
    (progn
      (setq result (vl-catch-all-apply 'vla-GetBoundingBox (list object 'minimum 'maximum)))
      (if (vl-catch-all-error-p result)
        "[]"
        (progn
          (setq minimum (vlax-safearray->list minimum) maximum (vlax-safearray->list maximum))
          (strcat "[" (rtos (car minimum) 2 6) "," (rtos (cadr minimum) 2 6) "," (rtos (car maximum) 2 6) "," (rtos (cadr maximum) 2 6) "]")
        )
      )
    )
  )
)

(defun ns-block-definition-bounds-json (data name / block next item pair point minimum-x minimum-y maximum-x maximum-y insertion scale-x scale-y rotation corners transformed x y)
  (setq block (tblobjname "BLOCK" name))
  (if (not block)
    "[]"
    (progn
      (setq next (entnext block) minimum-x nil minimum-y nil maximum-x nil maximum-y nil)
      (while next
        (setq item (entget next))
        (if (= (ns-value 0 item) "ENDBLK")
          (setq next nil)
          (progn
            (if (member (ns-value 0 item) '("LINE" "LWPOLYLINE" "POLYLINE" "ARC" "CIRCLE"))
              (foreach pair item
                (if (and (member (car pair) '(10 11 12 13)) (listp (cdr pair)) (numberp (car (cdr pair))))
                  (progn
                    (setq point (cdr pair) x (car point) y (cadr point))
                    (setq minimum-x (if minimum-x (min minimum-x x) x) minimum-y (if minimum-y (min minimum-y y) y))
                    (setq maximum-x (if maximum-x (max maximum-x x) x) maximum-y (if maximum-y (max maximum-y y) y))
                  )
                )
              )
            )
            (setq next (entnext next))
          )
        )
      )
      (if (not minimum-x)
        "[]"
        (progn
          (setq insertion (ns-value 10 data) scale-x (ns-value 41 data) scale-y (ns-value 42 data) rotation (ns-value 50 data))
          (if (not (numberp scale-x)) (setq scale-x 1.0))
          (if (not (numberp scale-y)) (setq scale-y 1.0))
          (if (not (numberp rotation)) (setq rotation 0.0))
          (setq corners (list (list minimum-x minimum-y) (list minimum-x maximum-y) (list maximum-x minimum-y) (list maximum-x maximum-y)))
          (setq minimum-x nil minimum-y nil maximum-x nil maximum-y nil)
          (foreach point corners
            (setq x (+ (car insertion) (- (* scale-x (car point) (cos rotation)) (* scale-y (cadr point) (sin rotation)))))
            (setq y (+ (cadr insertion) (+ (* scale-x (car point) (sin rotation)) (* scale-y (cadr point) (cos rotation)))))
            (setq minimum-x (if minimum-x (min minimum-x x) x) minimum-y (if minimum-y (min minimum-y y) y))
            (setq maximum-x (if maximum-x (max maximum-x x) x) maximum-y (if maximum-y (max maximum-y y) y))
          )
          (strcat "[" (rtos minimum-x 2 6) "," (rtos minimum-y 2 6) "," (rtos maximum-x 2 6) "," (rtos maximum-y 2 6) "]")
        )
      )
    )
  )
)
(defun ns-full-mtext (data / value pair)
  (setq value "")
  (foreach pair data (if (or (= (car pair) 1) (= (car pair) 3)) (setq value (strcat value (cdr pair)))))
  value
)

(defun ns-full-extended-text (data / value pair)
  (setq value "")
  (foreach pair data
    (if (member (car pair) '(1 3 300 301 302 303 304))
      (setq value (strcat value (if (= value "") "" " | ") (vl-princ-to-string (cdr pair))))
    )
  )
  value
)

(defun ns-table-code-summary (data / value pair)
  (setq value "")
  (foreach pair data
    (if (and (>= (car pair) 90) (<= (car pair) 99))
      (setq value (strcat value (if (= value "") "" " | ") (itoa (car pair)) "=" (vl-princ-to-string (cdr pair))))
    )
  )
  value
)

(defun ns-write-attributes (entity layout block handle layer / next data type count)
  (setq next (entnext entity))
  (setq count 0)
  (while (and next (< count 100))
    (setq data (entget next) type (ns-value 0 data))
    (cond
      ((= type "ATTRIB")
        (ns-write-line
          (strcat "{\"record\":\"block_attribute\",\"layout\":" (ns-json-string layout)
            ",\"block\":" (ns-json-string block) ",\"handle\":" (ns-json-string handle)
            ",\"tag\":" (ns-json-string (ns-value 2 data)) ",\"value\":" (ns-json-string (ns-full-mtext data))
            ",\"layer\":" (ns-json-string layer) "}")
        )
        (setq count (1+ count))
      )
      ((= type "SEQEND") (setq next nil))
      (T (setq next nil))
    )
    (if next (setq next (entnext next)))
  )
)

(defun ns-table-value-string (value)
  (cond
    ((vl-catch-all-error-p value) "")
    ((= (type value) 'VARIANT) (vl-princ-to-string (vlax-variant-value value)))
    (T (vl-princ-to-string value))
  )
)

(defun ns-write-table-cells (entity data layout handle layer / object rows columns row column value result dxf-rows dxf-columns)
  (setq dxf-rows (ns-value 91 data) dxf-columns (ns-value 92 data))
  (setq result (vl-catch-all-apply 'vlax-ename->vla-object (list entity)))
  (if (not (vl-catch-all-error-p result))
    (progn
      (setq object result)
      (setq rows (vl-catch-all-apply 'vla-get-Rows (list object)))
      (setq columns (vl-catch-all-apply 'vla-get-Columns (list object)))
      (if (vl-catch-all-error-p rows) (setq rows dxf-rows))
      (if (vl-catch-all-error-p columns) (setq columns dxf-columns))
      (ns-write-line
        (strcat "{\"record\":\"table_meta\",\"layout\":" (ns-json-string layout)
          ",\"handle\":" (ns-json-string handle) ",\"layer\":" (ns-json-string layer)
          ",\"objectName\":" (ns-json-string (ns-table-value-string (vl-catch-all-apply 'vla-get-ObjectName (list object))))
          ",\"rows\":" (if (numberp rows) (itoa rows) "0") ",\"columns\":" (if (numberp columns) (itoa columns) "0") "}")
      )
      (if (and (numberp rows) (numberp columns) (> rows 0) (> columns 0))
        (progn
          (setq row 0)
          (while (< row rows)
            (setq column 0)
            (while (< column columns)
              (setq value (vl-catch-all-apply 'vlax-invoke-method (list object 'GetText row column)))
              (if (vl-catch-all-error-p value) (setq value (vl-catch-all-apply 'vla-GetText (list object row column))))
              (setq value (ns-table-value-string value))
              (ns-write-line
                (strcat "{\"record\":\"table_cell\",\"layout\":" (ns-json-string layout)
                  ",\"handle\":" (ns-json-string handle) ",\"layer\":" (ns-json-string layer)
                  ",\"row\":" (itoa row) ",\"column\":" (itoa column) ",\"value\":" (ns-json-string value) "}")
              )
              (setq column (1+ column))
            )
            (setq row (1+ row))
          )
        )
      )
    )
  )
)

(defun ns-write-entity (entity / data type layout layer handle name text measurement point bounds)
  (setq data (entget entity) type (ns-value 0 data))
  (if (member type '("TEXT" "MTEXT" "INSERT" "ACAD_TABLE" "TABLE" "DIMENSION" "LEADER" "MULTILEADER"))
    (progn
      (setq layout (ns-value 410 data) layer (ns-value 8 data) handle (ns-value 5 data))
      (if (= layout "") (setq layout "Model"))
      (setq name (if (= type "INSERT") (ns-value 2 data) ""))
      (setq text
        (cond
          ((or (= type "TEXT") (= type "MTEXT") (= type "DIMENSION")) (ns-full-mtext data))
          ((or (= type "MULTILEADER") (= type "ACAD_TABLE") (= type "TABLE")) (ns-full-extended-text data))
          (T "")
        )
      )
      (setq measurement (if (= type "DIMENSION") (ns-value 42 data) ""))
      (setq point (ns-value 10 data))
      (setq bounds (if (and (= type "INSERT") (vl-string-search "TITLE BLOCK" (strcase name))) (ns-block-definition-bounds-json data name) "[]"))
      (ns-write-line
        (strcat "{\"record\":\"entity\",\"layout\":" (ns-json-string layout)
          ",\"type\":" (ns-json-string type) ",\"layer\":" (ns-json-string layer)
          ",\"handle\":" (ns-json-string handle) ",\"name\":" (ns-json-string name)
          ",\"text\":" (ns-json-string text)
          ",\"tableRows\":" (if (and (or (= type "ACAD_TABLE") (= type "TABLE")) (numberp (ns-value 91 data))) (itoa (ns-value 91 data)) "0")
          ",\"tableColumns\":" (if (and (or (= type "ACAD_TABLE") (= type "TABLE")) (numberp (ns-value 92 data))) (itoa (ns-value 92 data)) "0")
          ",\"measurement\":" (if (numberp measurement) (rtos measurement 2 8) "null")
          ",\"point\":" (ns-point-json point) ",\"bounds\":" bounds "}")
      )
      (if (and (= type "INSERT") (= (ns-value 66 data) 1)) (ns-write-attributes entity layout name handle layer))
      (if (or (= type "ACAD_TABLE") (= type "TABLE")) (ns-write-table-cells entity data layout handle layer))
    )
  )
)

(defun c:NSPEEREXTRACT (/ output-path selection index entity layouts layout)
  (setq output-path (getenv "NS_CAD_OUTPUT"))
  (if output-path
    (progn
      (setq ns-output-file (open output-path "w"))
      (setq selection (ssget "_X"))
      (setq index 0 layouts '())
      (if selection
        (while (< index (sslength selection))
          (setq entity (ssname selection index))
          (setq layout (ns-value 410 (entget entity)))
          (if (and (/= layout "") (not (member layout layouts))) (setq layouts (cons layout layouts)))
          (ns-write-entity entity)
          (setq index (1+ index))
        )
      )
      (foreach layout layouts (ns-write-line (strcat "{\"record\":\"layout\",\"name\":" (ns-json-string layout) "}")))
      (close ns-output-file)
      (setq ns-output-file nil)
    )
  )
  (princ)
)

(c:NSPEEREXTRACT)
(princ)
